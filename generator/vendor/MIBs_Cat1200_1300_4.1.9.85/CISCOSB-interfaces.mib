CISCOSB-rlInterfaces DEFINITIONS ::= BEGIN

-- Title: CISCOSB Switch Interfaces Private

IMPORTS
    ifIndex, InterfaceIndex, InterfaceIndexOrZero           FROM IF-MIB
    IANAifType                                              FROM IANAifType-MIB
    PortList                                                FROM Q-BRIDGE-MIB
    Unsigned32, Integer32, Counter32, Gauge32, TimeTicks,
    Counter64, MODULE-IDENTITY, OBJECT-TYPE                 FROM SNMPv2-SMI
    RowStatus, TruthValue, TEXTUAL-CONVENTION,
    DisplayString, PhysAddress, TimeStamp                   FROM SNMPv2-TC
    switch001, 	rlIfInterfaces                               FROM CISCOSB-MIB;


swInterfaces MODULE-IDENTITY
      LAST-UPDATED "201304010000Z"  -- April 1, 2013
                ORGANIZATION "Cisco Systems, Inc."
                CONTACT-INFO
                "Postal: 170 West Tasman Drive
                San Jose , CA 95134-1706
                USA

                
                Website:  Cisco Small Business Support Community <http://www.cisco.com/go/smallbizsupport>"

      DESCRIPTION
              "The MIB module describes the private MIB for Switch Interfaces supported
               by CISCOSB ROS software and products."
      REVISION     "201304010000Z"  -- April 1, 2013
      DESCRIPTION
              "Added MODULE-IDENTITY"
      ::= { switch001 43  }


-- These bits can be set in any combination (except unknown)
-- for field swIfAdminSpeedDuplexAutoNegotiationLocalCapabilities
-- and will take affect when field swIfSpeedDuplexAutoNegotiation
-- will be set to enabled.
-- In addition these fields can be read for operative values of
-- auto negotiation capabilities
AutoNegCapabilitiesBits ::= TEXTUAL-CONVENTION
    STATUS  current
    DESCRIPTION
        "Auto negotiation capabilities bits."
    SYNTAX BITS {
        default(0),
        unknown(1),
        tenHalf(2),
        tenFull(3),
        fastHalf(4),
        fastFull(5),
        gigaHalf(6),
        gigaFull(7),
        tenGigaFull(8),
        fiveGigaFull(9),
        twoPointFiveGigaFull(10),
		twentyFiveGigaFull(11),
		fortyGigaFull(12),
		fiftyGigaFull(13),
		oneHundredGigaFull(14),
		twoHundredGigaFull(15)
    }

--
-- swTable
--

swIfTable    OBJECT-TYPE
   SYNTAX  SEQUENCE  OF SwIfEntry
   MAX-ACCESS   not-accessible
   STATUS       current
   DESCRIPTION
    "Switch media specific information and configuration of the device
     interfaces."
   ::=  { swInterfaces 1 }

swIfEntry OBJECT-TYPE
   SYNTAX  SwIfEntry
   MAX-ACCESS   not-accessible
   STATUS       current
   DESCRIPTION
    "Defines the contents of each line in the swIfTable table."
   INDEX   { swIfIndex }
   ::=  { swIfTable 1 }

SwIfEntry ::= SEQUENCE {
        swIfIndex                                               INTEGER,
        swIfPhysAddressType                                     INTEGER,
        swIfDuplexAdminMode                                     INTEGER,
        swIfDuplexOperMode                                      INTEGER,
        swIfBackPressureMode                                    INTEGER,
        swIfTaggedMode                                          INTEGER,
        swIfTransceiverType                                     INTEGER,
        swIfLockAdminStatus                                     INTEGER,
        swIfLockOperStatus                                      INTEGER,
        swIfType                                                INTEGER,
        swIfDefaultTag                                          INTEGER,
        swIfDefaultPriority                                     INTEGER,
        swIfStatus                                              RowStatus,
        swIfFlowControlMode                                     INTEGER,
        swIfSpeedAdminMode                                      INTEGER,
        swIfSpeedDuplexAutoNegotiation                          INTEGER,
        swIfOperFlowControlMode                                 INTEGER,
        swIfOperSpeedDuplexAutoNegotiation                      INTEGER,
        swIfOperBackPressureMode                                INTEGER,
        swIfAdminLockAction                                     INTEGER,
        swIfOperLockAction                                      INTEGER,
        swIfAdminLockTrapEnable                                 TruthValue,
        swIfOperLockTrapEnable                                  TruthValue,
        swIfOperSuspendedStatus                                 TruthValue,
        swIfLockOperTrapCount                                   INTEGER,
        swIfLockAdminTrapFrequency                              INTEGER,
        swIfReActivate                                          TruthValue,
        swIfAdminMdix                                           INTEGER,
        swIfOperMdix                                            INTEGER,
        swIfHostMode                                            INTEGER,
        swIfSingleHostViolationAdminAction                      INTEGER,
        swIfSingleHostViolationOperAction                       INTEGER,
        swIfSingleHostViolationAdminTrapEnable                  TruthValue,
        swIfSingleHostViolationOperTrapEnable                   TruthValue,
        swIfSingleHostViolationOperTrapCount                    INTEGER,
        swIfSingleHostViolationAdminTrapFrequency               INTEGER,
        swIfLockLimitationMode                                  INTEGER,
        swIfLockMaxMacAddresses                                 INTEGER,
        swIfLockMacAddressesCount                               INTEGER,
        swIfAdminSpeedDuplexAutoNegotiationLocalCapabilities    AutoNegCapabilitiesBits,
        swIfOperSpeedDuplexAutoNegotiationLocalCapabilities     AutoNegCapabilitiesBits,
        swIfSpeedDuplexNegotiationRemoteCapabilities            AutoNegCapabilitiesBits,
        swIfAdminComboMode                                      INTEGER,
        swIfOperComboMode                                       INTEGER,
        swIfAutoNegotiationMasterSlavePreference                INTEGER,
        swIfPortCapabilities                                    AutoNegCapabilitiesBits,
	swIfPortStateDuration					INTEGER,
        swIfApNegotiationLane                                   INTEGER,
        swIfPortFecMode                                         INTEGER,
        swIfPortNumOfLanes                                      INTEGER,
		swIfPortAdminFecMode                                    INTEGER,
		swIfPortOperFecMode                                     INTEGER
        }


swIfIndex OBJECT-TYPE
    SYNTAX   INTEGER
    MAX-ACCESS  read-only
    STATUS      current
    DESCRIPTION
        "Index to the swIfTable. The interface defined by a
         particular value of this index is the same interface as
         identified by the same value of ifIndex (MIB II)."
    ::= {  swIfEntry 1  }

swIfPhysAddressType OBJECT-TYPE
    SYNTAX  INTEGER {
        default(1),
        reserve(2)
    }
    MAX-ACCESS  read-write
    STATUS      obsolete
    DESCRIPTION
        " This variable indicates whether the physical address assigned to this
          interface should be the default one or be chosen from the set of
          reserved physical addresses of the device."
    DEFVAL { default }
    ::= {  swIfEntry 2  }

swIfDuplexAdminMode  OBJECT-TYPE
    SYNTAX  INTEGER {
        none(1),
        half(2),
        full(3)
    }
    MAX-ACCESS  read-write
    STATUS      current
    DESCRIPTION
        "This variable specifies whether this interface should operate in
         half duplex or full duplex mode. This specification will take effect
         only if swIfSpeedDuplexAutoNegotiation is disabled.
         A value of 'none' is returned if a value of the variable
         hasn't been set."
    DEFVAL { none }
    ::= {  swIfEntry 3  }

swIfDuplexOperMode  OBJECT-TYPE
    SYNTAX  INTEGER {
        half(1),
        full(2),
        hybrid(3),
        unknown(4)
    }
    MAX-ACCESS  read-only
    STATUS      current
    DESCRIPTION
        " This variable indicates whether this interface operates in half
          duplex or full duplex mode.
          This variable can have the values hybrid or unknown
          only for a trunk.
          unknown - only if trunk operative status is not present."
    ::= {  swIfEntry 4  }

swIfBackPressureMode OBJECT-TYPE
    SYNTAX  INTEGER {
        enable(1),
        disable(2)
    }
    MAX-ACCESS  read-write
    STATUS      current
    DESCRIPTION
        "This variable indicates whether this interface activates back pressure
         when congested."
    ::= {  swIfEntry 5 }

swIfTaggedMode OBJECT-TYPE
    SYNTAX  INTEGER {
        enable(1),
        disable(2)
    }
    MAX-ACCESS  read-write
    STATUS      current
    DESCRIPTION
        "If enable, this interface operates in tagged mode, i.e all frames sent
         out through this interface will have the 802.1Q header.
         If disabled the frames will not be tagged."
    DEFVAL { disable }
    ::= {  swIfEntry 6 }

swIfTransceiverType  OBJECT-TYPE
    SYNTAX  INTEGER {
        regular(1),
        fiberOptics(2),
        comboRegular(3),
        comboFiberOptics(4)
    }
    MAX-ACCESS  read-only
    STATUS      current
    DESCRIPTION
        " This variable indicates the transceiver type of this interface."
    ::= {  swIfEntry 7  }

swIfLockAdminStatus OBJECT-TYPE
    SYNTAX  INTEGER {
       locked(1),
       unlocked(2)
    }
    MAX-ACCESS  read-write
    STATUS      current
    DESCRIPTION
        "This variable indicates whether this interface should operate in locked
         or unlocked mode.
         In unlocked mode the device learns all MAC addresses from this port and
         forwards all frames arrived at this port. In locked mode no new MAC
         addresses are learned and only frames with known source MAC
         addresses are forwarded."
    DEFVAL { unlocked }
    ::= {  swIfEntry 8 }

swIfLockOperStatus OBJECT-TYPE
    SYNTAX  INTEGER {
        locked(1),
        unlocked(2)
    }
    MAX-ACCESS  read-only
    STATUS      current
    DESCRIPTION
        "This variable defines whether this interface operates in locked
         or unlocked mode. It is locked in each of the following two cases:
             1) if swLockAdminStatus  is set to locked
             2) no IP/IPX interface is defined over this interface and no
                VLAN contains this interface.
         In unlocked mode the device learns all MAC addresses from this port and
         forwards all frames arrived at this port. In locked mode no new MAC
         addresses are learned and only frames with known source MAC
         addresses are forwarded."
    ::= {  swIfEntry 9 }

swIfType  OBJECT-TYPE
    SYNTAX  INTEGER {
        eth10M(1),
        eth100M(2),
        eth1000M(3),
        eth2500M(4),
        eth5G(5),
        eth10G(6),
        eth20G(7),
        eth40G(8),
        eth100G(9),
        eth25G(10),
        eth50G(11),
        unknown(12)
    }
    MAX-ACCESS  read-only
    STATUS      current
    DESCRIPTION
        " This variable specifies the type of interface."
    ::= {  swIfEntry 10 }

swIfDefaultTag  OBJECT-TYPE
    SYNTAX  INTEGER (0..4095)
    MAX-ACCESS  read-only
    STATUS      current
    DESCRIPTION
        "This variable specifies the default VLAN tag which will be attached
         to outgoing frames if swIfTaggedMode for this interface is enabled."
    DEFVAL { 0 }
    ::= {  swIfEntry 11 }

swIfDefaultPriority  OBJECT-TYPE
    SYNTAX  INTEGER (0..7)
    MAX-ACCESS  read-write
    STATUS      current
    DESCRIPTION
        " This variable specifies the default port priority."
    DEFVAL { 0 }
    ::= { swIfEntry 12 }

swIfStatus OBJECT-TYPE
   SYNTAX  RowStatus
   MAX-ACCESS   read-write
   STATUS       current
   DESCRIPTION
       "The status of a table entry.
        It is used to delete an entry from this table."
  ::= { swIfEntry 13 }

swIfFlowControlMode OBJECT-TYPE
   SYNTAX  INTEGER {
      on(1),
      off(2),
      autoNegotiation(3),
      enabledRx(4),
      enabledTx(5)
   }
   MAX-ACCESS   read-write
   STATUS       current
   DESCRIPTION
       "on - Flow control will be enabled on this interface according to the
             IEEE 802.3x standard.
        off - Flow control is disabled.
        autoNegotiation - Flow control will be enabled or disabled on this
                          interface. If enabled, it will operate as specified
                          by the IEEE 802.3x standard.
        enabledRx - Flow control will be enabled on this interface for
                    recieved frames.
        enabledTx - Flow control will be enabled on this interface for
                    transmitted frames.
        An attempt to set this object to 'enabledRx(4)' or 'enabledTx(5)'
        will fail on interfaces that do not support operation
        at greater than 100 Mb/s.
        In any case, flow control can work only if swIfDuplexOperMode is
        full."
   ::= { swIfEntry  14}

swIfSpeedAdminMode OBJECT-TYPE
   SYNTAX  INTEGER
   MAX-ACCESS   read-write
   STATUS       current
   DESCRIPTION
        "This variable specifies the required speed of this interface in bits
         per second. This specification will take effect only if
         swIfSpeedDuplexAutoNegotiation is disabled.
         A value of 10 is returned for 10G.
         A value of 0 is returned if the value of the variable
         hasn't been set."
   DEFVAL { 0 }
  ::= { swIfEntry  15 }

swIfSpeedDuplexAutoNegotiation OBJECT-TYPE
   SYNTAX  INTEGER {
        enabled(1),
        disabled(2)
   }
   MAX-ACCESS   read-write
   STATUS       current
   DESCRIPTION
       "If enabled the speed and duplex mode will be set by the device through
       the autonegotiation process. Otherwise these characteristics will be
       set according to the values of swIfSpeedAdminMode and
       swIfSpeedDuplexAutoNegotiation."
  ::= { swIfEntry 16 }

swIfOperFlowControlMode OBJECT-TYPE
   SYNTAX  INTEGER {
      on(1),
      off(2),
      enabledRx(3),
      enabledTx(4)
   }
   MAX-ACCESS   read-only
   STATUS       current
   DESCRIPTION
       "on - Flow control is enabled on this interface according to the
             IEEE 802.3x standard.
        off - Flow control is disabled.
        enabledRx - Flow control is enabled on this interface for
                    recieved frames.
        enabledTx - Flow control is enabled on this interface for
                    transmitted frames."
  ::= { swIfEntry  17}

swIfOperSpeedDuplexAutoNegotiation OBJECT-TYPE
   SYNTAX  INTEGER {
        enabled(1),
        disabled(2),
        hybrid(3),
        unknown(4)
   }
   MAX-ACCESS   read-only
   STATUS       current
   DESCRIPTION
       "If enabled the speed and duplex are determined by the device through
       the autonegotiation process.
       If disabled these characteristics are determined according to the values
       of swIfSpeedAdminMode and swIfDuplexAdminMode.
       hybrid - only for a trunk.
       unknown -  only for ports that there operative status is not present."
  ::= { swIfEntry 18 }

swIfOperBackPressureMode OBJECT-TYPE
    SYNTAX  INTEGER {
        enable(1),
        disable(2),
        hybrid(3),
        unknown(4)
    }
    MAX-ACCESS  read-only
    STATUS      current
    DESCRIPTION
        "This variable indicates the operative back pressure mode of
         this interface."
    ::= {  swIfEntry 19 }

swIfAdminLockAction OBJECT-TYPE
    SYNTAX  INTEGER {
        discard(1),
        forwardNormal(2),
        discardDisable(3)
    }
    MAX-ACCESS  read-write
    STATUS      current
    DESCRIPTION
        "This variable indicates which action this interface should be taken
        in locked mode and therefore relevant only in locked mode.
        Possible actions:
        discard(1) - every packet is dropped.
        forwardNormal(2) - every packet is forwarded according to the DST address.
        discardDisable(3) - drops the first packet and suspends the port."
    --DEFVAL { discard } changed to product specific
    ::= {  swIfEntry 20 }


swIfOperLockAction OBJECT-TYPE
    SYNTAX  INTEGER {
        discard(1),
        forwardNormal (2),
        discardDisable(3)
    }
    MAX-ACCESS  read-only
    STATUS      current
    DESCRIPTION
        "This variable indicates which action this interface actually takes in
        locked mode and therefore relevant only in locked mode.
        Possible actions:
        discard(1) - every packet is dropped.
        forwardNormal(2) - every packet is forwarded according to the DST address.
        discardDisable(3) - drops the first packet and suspends the port."
    ::= {  swIfEntry 21 }


swIfAdminLockTrapEnable OBJECT-TYPE
    SYNTAX  TruthValue
    MAX-ACCESS  read-write
    STATUS      current
    DESCRIPTION
        "This variable indicates whether to create a SNMP trap in the locked mode."
    --DEFVAL { false } changed to product specific
    ::= {  swIfEntry 22 }

swIfOperLockTrapEnable OBJECT-TYPE
    SYNTAX  TruthValue
    MAX-ACCESS  read-only
    STATUS      current
    DESCRIPTION
        "This variable indicates whether a SNMP trap can be created in the
        locked mode."
    ::= {  swIfEntry 23 }

swIfOperSuspendedStatus OBJECT-TYPE
    SYNTAX  TruthValue
    MAX-ACCESS  read-only
    STATUS      current
    DESCRIPTION
        "This variable indicates whether the port is suspended or not due to some
        feature. After reboot this value is false"
    ::= {  swIfEntry 24 }

swIfLockOperTrapCount  OBJECT-TYPE
    SYNTAX  INTEGER (0 .. 2147483647 )
    MAX-ACCESS  read-only
    STATUS      current
    DESCRIPTION
        "This variable indicates the trap counter status per ifIndex
        (i.e. number of received packets since the last trap sent due to a
        packet which was received on this ifIndex). It's relevant only in locked
        mode while trap is enabled."
    ::= {  swIfEntry 25 }

swIfLockAdminTrapFrequency OBJECT-TYPE
    SYNTAX  INTEGER (1 .. 1000000)
--    UNITS    "seconds"
    MAX-ACCESS  read-write
    STATUS      current
    DESCRIPTION
        "This variable indicates the minimal frequency (in seconds) of sending
        a trap per ifIndex. It's relevant only in locked  mode and in trap
        enabled."
    --DEFVAL { 10 } changed to product specific
    ::= {  swIfEntry 26 }

swIfReActivate OBJECT-TYPE
    SYNTAX  TruthValue
    MAX-ACCESS  read-write
    STATUS      current
    DESCRIPTION
        "This variable reactivates (enables) an ifIndex (which was suspended)"
    DEFVAL { false }
    ::= {  swIfEntry 27 }

swIfAdminMdix OBJECT-TYPE
   SYNTAX  INTEGER {
      cross(1),
      normal(2),
      auto(3)
   }
   MAX-ACCESS   read-write
   STATUS       current
   DESCRIPTION
       "The configuration is on a physical port, not include trunks.
        cross  - The interface should force crossover.
        normal - The interface should not force crossover.
        auto    - Auto mdix is enabled on the interface."
   ::= { swIfEntry 28 }

swIfOperMdix OBJECT-TYPE
   SYNTAX  INTEGER {
      cross(1),
      normal(2),
      unknown(3)
   }
   MAX-ACCESS   read-only
   STATUS       current
   DESCRIPTION
       "cross  - The interface is in crossover mode.
        normal - The interface is not in crossover mode.
        unknown - Only for port that its operative status is not present
                  or down."
   ::= { swIfEntry 29 }

swIfHostMode OBJECT-TYPE
    SYNTAX  INTEGER {
       single(1),
       multiple(2),
       multiple-auth(3)
    }
    MAX-ACCESS  read-write
    STATUS      current
    DESCRIPTION
        "This variable indicates the 802.1X host mode of a port. Relevant when the port's 802.1X control is auto.
        In addtion multiple-auth was added."
    DEFVAL { single }
    ::= {  swIfEntry 30 }

swIfSingleHostViolationAdminAction OBJECT-TYPE
    SYNTAX  INTEGER {
       discard(1),
       forwardNormal (2),
       discardDisable(3)
    }
    MAX-ACCESS  read-write
    STATUS      current
    DESCRIPTION
        "This variable indicates which action this interface should take in single authorized.
        Possible actions:
        discard - every packet is dropped.
        forwardNormal - every packet is forwarded according to the DST address.
        discardDisable - drops the first packet and suspends the port."
    DEFVAL { discard }
    ::= {  swIfEntry 31 }

swIfSingleHostViolationOperAction OBJECT-TYPE
    SYNTAX  INTEGER {
       discard(1),
       forwardNormal (2),
       discardDisable(3)
    }
    MAX-ACCESS  read-only
    STATUS      current
    DESCRIPTION
        "This variable indicates which action this interface actually takes in single authorized.
        Possible actions:
        discard(1) - every packet is dropped.
        forwardNormal(2) - every packet is forwarded according to the DST address.
        discardDisable(3) - drops the first packet and suspends the port."
    DEFVAL { discard }
    ::= {  swIfEntry 32 }

swIfSingleHostViolationAdminTrapEnable OBJECT-TYPE
    SYNTAX  TruthValue
    MAX-ACCESS  read-write
    STATUS      current
    DESCRIPTION
        "This variable indicates whether to create a SNMP trap in single authorized."
    DEFVAL { false }
    ::= {  swIfEntry 33 }

swIfSingleHostViolationOperTrapEnable OBJECT-TYPE
    SYNTAX  TruthValue
    MAX-ACCESS  read-only
    STATUS      current
    DESCRIPTION
        "This variable indicates whether a SNMP trap can be created in the single authorized."
    ::= {  swIfEntry 34 }

swIfSingleHostViolationOperTrapCount OBJECT-TYPE
    SYNTAX  INTEGER (0 .. 2147483647)
    MAX-ACCESS  read-only
    STATUS      current
    DESCRIPTION
        "This variable indicates the trap counter status per ifIndex
        (i.e. number of received packets since the last trap sent due to a packet
        which was received on this ifIndex). It's relevant only in single authorized
        while trap is enabled."
    ::= {  swIfEntry 35 }

swIfSingleHostViolationAdminTrapFrequency OBJECT-TYPE
    SYNTAX  INTEGER (0 .. 1000000)
 -- UNITS    "seconds"
    MAX-ACCESS  read-write
    STATUS      current
    DESCRIPTION
        "This variable indicates the minimal frequency (in seconds) of sending a
        trap per ifIndex. It's relevant only in single authorized and in trap enabled.
        A value of 0 means that trap is disabled."
    DEFVAL { 0 }
    ::= {  swIfEntry 36 }

swIfLockLimitationMode OBJECT-TYPE
    SYNTAX  INTEGER {
        disabled(1),
        dynamic(2),
        secure-permanent(3),
        secure-delete-on-reset(4)
    }
    MAX-ACCESS   read-write
    STATUS   current
    DESCRIPTION
        "This variable indicates what is the learning limitation on the locked interface.
        Possible values:
        disabled - learning is stopped. The dynamic addresses associated with the
            port are not aged out or relearned on other port as long as the port is
            locked.
        dynamic - dynamic addresses can be learned up to the maximum dynamic addresses
            allowed on the port. Relearning and aging of the dynamic addresses are
            enabled. The learned addresses aren't kept after reset.
        secure-permanent - secure addresses can be learned up to the maximum addresses
            allowed on the port. Relearning and aging of addresses are disabled.
            The learned addresses are kept after reset.
        secure-delete-on-reset - secure addresses can be learned up to the maximum addresses
            allowed on the port. Relearning and aging of addresses are disabled.
            The learned addresses are not kept after reset."
    --DEFVAL { disabled } changed to product specific
    ::= {  swIfEntry 37 }

swIfLockMaxMacAddresses OBJECT-TYPE
    SYNTAX  INTEGER (0 .. 2147483647)
    MAX-ACCESS  read-write
    STATUS      current
    DESCRIPTION
        "This variable defines the maximum number of dynamic addresses that
        can be asscoiated with the locked interface. It isn't relevant in
        disabled limitation mode."
    DEFVAL { 1 }
    ::= {  swIfEntry 38 }

swIfLockMacAddressesCount OBJECT-TYPE
    SYNTAX  INTEGER (0 .. 2147483647)
    MAX-ACCESS  read-only
    STATUS      current
    DESCRIPTION
        "This variable indicates the actual number of dynamic addresses that can
        be asscoiated with the locked interface. It isn't relevant in disabled
        limitation mode."
    ::= {  swIfEntry 39 }

swIfAdminSpeedDuplexAutoNegotiationLocalCapabilities OBJECT-TYPE
    SYNTAX AutoNegCapabilitiesBits
    MAX-ACCESS   read-write
    STATUS       current
    DESCRIPTION
        "Administrative auto negotiation capabilities of the interface that can be advertised when
        swIfSpeedDuplexAutoNegotiation is enabled.
        default bit means advertise all the port's capabilities
        according to its type."
    DEFVAL { {default} }
    ::= { swIfEntry 40 }

swIfOperSpeedDuplexAutoNegotiationLocalCapabilities OBJECT-TYPE
    SYNTAX AutoNegCapabilitiesBits
    MAX-ACCESS   read-only
    STATUS       current
    DESCRIPTION
        "Operative auto negotiation capabilities of the remote link.
        unknown bit means that port operative status is not up."
    ::= { swIfEntry 41 }

swIfSpeedDuplexNegotiationRemoteCapabilities OBJECT-TYPE
    SYNTAX AutoNegCapabilitiesBits
    MAX-ACCESS   read-only
    STATUS       current
    DESCRIPTION
        "Operative auto negotiation capabilities of the remote link.
        unknown bit means that port operative status is not up,
        or auto negotiation process not complete,
        or remote link is not auto negotiation able."
    ::= { swIfEntry 42 }

swIfAdminComboMode  OBJECT-TYPE
    SYNTAX  INTEGER {
        force-fiber(1),
        force-copper(2),
        prefer-fiber(3),
        prefer-copper(4)
    }
    MAX-ACCESS  read-write
    STATUS      current
    DESCRIPTION
        "This variable specifies the administrative mode of a combo Ethernet interface."
    DEFVAL { prefer-fiber }
    ::= {  swIfEntry 43  }

swIfOperComboMode  OBJECT-TYPE
    SYNTAX  INTEGER {
        fiber(1),
        copper(2),
        unknown(3)
    }
    MAX-ACCESS  read-only
    STATUS      current
    DESCRIPTION
        "This variable specifies the operative mode of a combo Ethernet interface."
    ::= {  swIfEntry 44  }

swIfAutoNegotiationMasterSlavePreference OBJECT-TYPE
    SYNTAX  INTEGER {
        preferMaster(1),
        preferSlave(2)
    }
    MAX-ACCESS  read-write
    STATUS      current
    DESCRIPTION
        "This variable specifies the administrative mode of the Maste-Slave preference in auto negotiation."
--    DEFVAL - according to MTSC parameter
    ::= {  swIfEntry 45 }

swIfPortCapabilities OBJECT-TYPE
    SYNTAX AutoNegCapabilitiesBits
    MAX-ACCESS   read-only
    STATUS       current
    DESCRIPTION
        "Returns the port capabilities."
    ::= { swIfEntry 46 }


swIfPortStateDuration OBJECT-TYPE
    SYNTAX   INTEGER
    MAX-ACCESS  read-only
    STATUS      current
    DESCRIPTION
        "The amount of time(in sec) that a port has been up or down."
    ::= {  swIfEntry 47  }

swIfApNegotiationLane OBJECT-TYPE
    SYNTAX  INTEGER {
        laneZero(0),
        laneOne(1),
        laneTwo(2),
        laneThree(3)
    }
    MAX-ACCESS  read-write
    STATUS       current
    DESCRIPTION
        "which lane is used to perform negotiation in AP mode."
    DEFVAL { laneZero }
    ::= { swIfEntry 48}

swIfPortFecMode OBJECT-TYPE
    SYNTAX  INTEGER {
        fc(1),
        rs(2),
        none(3),
        rs-544-514(4),
		default(128)
    }
    MAX-ACCESS  read-write
    STATUS       current
    DESCRIPTION
        "determine fec (error correction) mode."
    ::= { swIfEntry 49 }

swIfPortNumOfLanes OBJECT-TYPE
    SYNTAX  INTEGER {
        oneLane(1),
        twoLanes(2),
        fourLanes(4),
		eightLanes(8),
		default(128)
    }
    MAX-ACCESS  read-write
    STATUS       current
    DESCRIPTION
        "determine number of lanes to configure interface mode."
	DEFVAL { default }
    ::= { swIfEntry 50 }

	swIfPortAdminFecMode OBJECT-TYPE
    SYNTAX  INTEGER {
        not-supported(1),
		off(2),
        auto-neg(3),
        cl74(4),
        cl91(5),
		kp(6)
    }
    MAX-ACCESS  read-only
    STATUS       current
    DESCRIPTION
        "determine fec (error correction) admin mode."
    ::= { swIfEntry 51 }

	swIfPortOperFecMode OBJECT-TYPE
    SYNTAX  INTEGER {
        not-supported(1),
		off(2),
        auto-neg(3),
        cl74(4),
        cl91(5),
		kp(6)
    }
    MAX-ACCESS  read-only
    STATUS       current
    DESCRIPTION
        "determine fec (error correction) operational mode."
    ::= { swIfEntry 52 }


--
-- swIfMibVersion
--
swIfMibVersion OBJECT-TYPE
    SYNTAX  INTEGER
    MAX-ACCESS  read-only
    STATUS      current
    DESCRIPTION
        "The swIfTable Mib's version, the current version is 3."
    ::= { swInterfaces 2 }


--
-- swIfPortLockSupport
--
swIfPortLockSupport OBJECT-TYPE
    SYNTAX  INTEGER {
        supported (1),
        notSupported (2)
    }
    MAX-ACCESS  read-only
    STATUS      current
    DESCRIPTION
        "indicates if the locked port package is supported."
    ::= { swInterfaces 3 }


--
-- swIfPortLockActionSupport
--
swIfPortLockActionSupport OBJECT-TYPE
    SYNTAX      OCTET STRING (SIZE(1))
    MAX-ACCESS  read-only
    STATUS      current
    DESCRIPTION
        "indicates which port lock actions are supported:
                (bit 0 is the most significant bit)
            bit 0 - discard
            bit 1 - forwardNormal
            bit 2 - discardDisable"
    ::= { swInterfaces 4 }


--
-- swIfPortLockTrapSupport
--
swIfPortLockTrapSupport OBJECT-TYPE
    SYNTAX      OCTET STRING (SIZE(1))
    MAX-ACCESS  read-only
    STATUS      current
    DESCRIPTION
        "indicates with which port lock actions the trap option is supported
        (e.g. discard indicates that trap is supported only when the portlock
         action is discard):
                (bit 0 is the most significant bit)
            bit 0 - discard
            bit 1 - forwardNormal
            bit 2 - discardDisable"
    ::= { swInterfaces 5 }



--
-- swIfPortLockIfRangeTable
--
swIfPortLockIfRangeTable    OBJECT-TYPE
   SYNTAX  SEQUENCE  OF SwIfPortLockIfRangeEntry
   MAX-ACCESS   not-accessible
   STATUS       current
   DESCRIPTION
    "Port lock interfaces range configuration"
   ::=  { swInterfaces 6 }

swIfPortLockIfRangeEntry OBJECT-TYPE
   SYNTAX  SwIfPortLockIfRangeEntry
   MAX-ACCESS   not-accessible
   STATUS       current
   DESCRIPTION
    "Defines the contents of each line in the swIfPortLockIfRangeTable table."
   INDEX   { swIfPortLockIfRangeIndex }
   ::=  { swIfPortLockIfRangeTable 1 }

SwIfPortLockIfRangeEntry ::= SEQUENCE {
        swIfPortLockIfRangeIndex           INTEGER,
        swIfPortLockIfRange                PortList,
        swIfPortLockIfRangeLockStatus      INTEGER,
        swIfPortLockIfRangeAction          INTEGER,
        swIfPortLockIfRangeTrapEn          TruthValue,
        swIfPortLockIfRangeTrapFreq        INTEGER
    }

swIfPortLockIfRangeIndex OBJECT-TYPE
    SYNTAX   INTEGER
    MAX-ACCESS  read-only
    STATUS      current
    DESCRIPTION
        "Index to the swIfPortLockIfRangeTable."
    ::= {  swIfPortLockIfRangeEntry 1  }

swIfPortLockIfRange OBJECT-TYPE
    SYNTAX      PortList
    MAX-ACCESS  read-write
    STATUS      current
    DESCRIPTION
        "The set of interfaces to which the port lock parameters should be configured"
    ::= { swIfPortLockIfRangeEntry 2 }

swIfPortLockIfRangeLockStatus OBJECT-TYPE
    SYNTAX  INTEGER {
       locked(1),
       unlocked(2)
    }
    MAX-ACCESS  read-write
    STATUS      current
    DESCRIPTION
        "This variable indicates whether the interfaces range should operate in locked
         or unlocked mode.
         In unlocked mode the device learns all MAC addresses from these interfaces and
         forwards all frames arrived at these interfaces. In locked mode no new MAC
         addresses are learned and only frames with known source MAC
         addresses are forwarded."
    DEFVAL { unlocked }
    ::= { swIfPortLockIfRangeEntry 3 }

swIfPortLockIfRangeAction OBJECT-TYPE
    SYNTAX  INTEGER {
        discard(1),
        forwardNormal(2),
        discardDisable(3)
    }
    MAX-ACCESS  read-write
    STATUS      current
    DESCRIPTION
        "This variable indicates which action for these interfaces should be take
        in locked mode and therefore relevant only in locked mode.
        Possible actions:
        discard(1) - every packet is dropped.
        forwardNormal(2) - every packet is forwarded according to the DST address.
        discardDisable(3) - drops the first packet and suspends the port."
    --DEFVAL { discard } changed to product specific
    ::= {  swIfPortLockIfRangeEntry 4 }

swIfPortLockIfRangeTrapEn OBJECT-TYPE
    SYNTAX  TruthValue
    MAX-ACCESS  read-write
    STATUS      current
    DESCRIPTION
        "This variable indicates whether to create a SNMP trap in the locked mode."
    --DEFVAL { false } changed to product specific
    ::= {  swIfPortLockIfRangeEntry 5 }

swIfPortLockIfRangeTrapFreq OBJECT-TYPE
    SYNTAX  INTEGER (1 .. 1000000)
--    UNITS    "seconds"
    MAX-ACCESS  read-write
    STATUS      current
    DESCRIPTION
        "This variable indicates the minimal frequency (in seconds) of sending
        a trap for these interfaces. It's relevant only in locked  mode and in trap
        enabled."
    --DEFVAL { 10 } changed to product specific
    ::= {  swIfPortLockIfRangeEntry 6 }

--
-- swIfExtTable
--

swIfExtTable    OBJECT-TYPE
    SYNTAX  SEQUENCE  OF SwIfExtEntry
    MAX-ACCESS   not-accessible
    STATUS       current
    DESCRIPTION
        "Display information and configuration of the device interfaces."
    ::=  { swInterfaces 7 }

swIfExtEntry OBJECT-TYPE
    SYNTAX  SwIfExtEntry
    MAX-ACCESS   not-accessible
    STATUS       current
    DESCRIPTION
        "Defines the contents of each row in the swIfExtTable."
    INDEX   { ifIndex }
    ::=  { swIfExtTable 1 }

SwIfExtEntry ::= SEQUENCE {
        swIfExtSFPSpeed    INTEGER
    }

swIfExtSFPSpeed OBJECT-TYPE
    SYNTAX  INTEGER {
        default(1),
        eth100M(2),
        eth1G(3)
    }
    MAX-ACCESS  read-write
    STATUS      current
    DESCRIPTION
        "Configure speed of an SFP Ethernet interface."
    DEFVAL { default }
    ::= {  swIfExtEntry 1  }

--
-- rlIfInterfaces
--

rlIfMibVersion OBJECT-TYPE
    SYNTAX  INTEGER
    MAX-ACCESS  read-only
    STATUS      current
    DESCRIPTION
        "MIB's version, the current version is 1."
    ::= { rlIfInterfaces 1 }

rlIfNumOfPhPorts OBJECT-TYPE
    SYNTAX INTEGER
    MAX-ACCESS  read-only
    STATUS      current
    DESCRIPTION
        "Total number of physical ports on this device
         (including all stack units)"
    ::= { rlIfInterfaces 2 }

rlIfMapOfOnPhPorts OBJECT-TYPE
    SYNTAX OCTET STRING
    MAX-ACCESS          read-only
    STATUS      current
    DESCRIPTION
       "Each bit in this octet string indicates that the correspondig port's
        ifOperStatus is ON if set.
        The mapping of port number to bits in this octet string is as follows:
        The port with the L2 interface number 1 is mapped to the least
        significant bit of the 1st octet, the port with L2 ifNumber 2 to the
        next significant bit in the 1st octet, port 8 to the most-significant
        bit of the in the 1st octet, port 9 to the least
        significant bit of the 2nd octet, etc. and in general,
        port n to bit corresponding to 2**((n mod 8) -1) in byte n/8 + 1"
    ::= { rlIfInterfaces 3 }

rlIfClearPortMibCounters OBJECT-TYPE
    SYNTAX      PortList
    MAX-ACCESS  read-write
    STATUS      current
    DESCRIPTION
        "Each bit that is set in this portList represent a port that
         its mib counters should be reset."
    ::= { rlIfInterfaces 4 }

rlIfNumOfUserDefinedPorts OBJECT-TYPE
    SYNTAX INTEGER
    MAX-ACCESS  read-only
    STATUS      current
    DESCRIPTION
        "The number of user defined ports on this device."
    ::= { rlIfInterfaces 5 }

rlIfFirstOutOfBandIfIndex OBJECT-TYPE
    SYNTAX INTEGER
    MAX-ACCESS          read-only
    STATUS      current
    DESCRIPTION
        "First ifIndex of out-of-band port.
         This scalar exists only the device has out of band ports."
    ::= { rlIfInterfaces 6 }

rlIfNumOfLoopbackPorts OBJECT-TYPE
    SYNTAX      INTEGER
    MAX-ACCESS  read-only
    STATUS      current
    DESCRIPTION
        "The number of loopback ports on this device."
    ::= { rlIfInterfaces 7 }

rlIfFirstLoopbackIfIndex OBJECT-TYPE
    SYNTAX INTEGER
    MAX-ACCESS  read-only
    STATUS      current
    DESCRIPTION
        "First ifIndex of loopback port.
         This scalar will exists only if rlIfNumOfLoopbackPorts
         is different from 0."
    ::= { rlIfInterfaces 8 }

rlIfExistingPortList OBJECT-TYPE
    SYNTAX      PortList
    MAX-ACCESS  read-only
    STATUS      current
    DESCRIPTION
        "Indicates which ports/trunks exist in the system.
         It doesn't indicate which are present."
    ::= { rlIfInterfaces 9 }

rlIfBaseMACAddressPerIfIndex OBJECT-TYPE
    SYNTAX      TruthValue
    MAX-ACCESS  read-write
    STATUS      current
    DESCRIPTION
        "Indicates if the system will assign a unique MAC per Ethernet port or not."
    ::= { rlIfInterfaces 10 }

rlFlowControlCascadeMode OBJECT-TYPE
    SYNTAX      INTEGER {
        enabled(1),
        disabled(2)
        }
    MAX-ACCESS  read-write
    STATUS      current
    DESCRIPTION
        "enable disable flow control on cascade ports"
    ::= { rlIfInterfaces 11 }

rlFlowControlCascadeType OBJECT-TYPE
    SYNTAX      INTEGER {
        internalonly(1),
        internalexternal(2)
        }
    MAX-ACCESS  read-write
    STATUS      current
    DESCRIPTION
        "define which type of ports will be affected by flow control on cascade ports"
    ::= { rlIfInterfaces 12 }

rlFlowControlRxPerSystem OBJECT-TYPE
    SYNTAX      TruthValue
    MAX-ACCESS  read-write
    STATUS      current
    DESCRIPTION
        "define if flow control RX is supported per system."
    ::= { rlIfInterfaces 13 }

rlCascadePortProtectionAction OBJECT-TYPE
    SYNTAX      TruthValue
    MAX-ACCESS  read-write
    STATUS      current
    DESCRIPTION
        "As a result of this set all of the local cascade ports
         will stop being consider unstable and will be force up."
    ::= { rlIfInterfaces 14 }

rlManagementIfIndex OBJECT-TYPE
    SYNTAX      InterfaceIndex
    MAX-ACCESS  read-write
    STATUS      current
    DESCRIPTION
        "Specify L2 bound management interface index in a single IP address system
        when configurable management interface is supported."
    ::= { rlIfInterfaces 15 }

rlIfClearStackPortsCounters OBJECT-TYPE
    SYNTAX      TruthValue
    MAX-ACCESS  read-write
    STATUS      current
    DESCRIPTION
        "As a result of this set all counters of
         all external cascade ports will be cleared."
    ::= { rlIfInterfaces 16 }

rlIfClearPortMacAddresses OBJECT-TYPE
    SYNTAX      InterfaceIndexOrZero
    MAX-ACCESS  read-write
    STATUS      current
    DESCRIPTION
         "if port is non secure, its all dynamic MAC addresses are cleared.
          if port is secure, its all secure MAC addresses which have learned or configured are cleared."
    ::= { rlIfInterfaces 17 }

rlIfCutThroughPacketLength OBJECT-TYPE
    SYNTAX      INTEGER (257 .. 16383)
    MAX-ACCESS  read-write
--              Obsolete
    STATUS      current
    DESCRIPTION
        "The default packet length that is assigned to a packet in the
         Cut-Through mode."
    DEFVAL { 1522 }
    ::= { rlIfInterfaces 18 }

rlIfCutPriorityZero OBJECT-TYPE
    SYNTAX      TruthValue
    MAX-ACCESS  read-write
    STATUS      current
    DESCRIPTION
        "Enable or disable cut-Through for priority 0."
    DEFVAL { false }
    ::= { rlIfInterfaces 19 }

rlIfCutPriorityOne OBJECT-TYPE
    SYNTAX      TruthValue
    MAX-ACCESS  read-write
    STATUS      current
    DESCRIPTION
        "Enable or disable cut-Through for priority 1."
    DEFVAL { false }
    ::= { rlIfInterfaces 20 }

rlIfCutPriorityTwo OBJECT-TYPE
    SYNTAX      TruthValue
    MAX-ACCESS  read-write
    STATUS      current
    DESCRIPTION
        "Enable or disable cut-Through for priority 2."
    DEFVAL { false }
    ::= { rlIfInterfaces 21 }

rlIfCutPriorityThree OBJECT-TYPE
    SYNTAX      TruthValue
    MAX-ACCESS  read-write
    STATUS      current
    DESCRIPTION
        "Enable or disable cut-Through for priority 3."
    DEFVAL { false }
    ::= { rlIfInterfaces 22 }

rlIfCutPriorityFour OBJECT-TYPE
    SYNTAX      TruthValue
    MAX-ACCESS  read-write
    STATUS      current
    DESCRIPTION
        "Enable or disable cut-Through for priority 4."
    DEFVAL { false }
    ::= { rlIfInterfaces 23 }

rlIfCutPriorityFive OBJECT-TYPE
    SYNTAX      TruthValue
    MAX-ACCESS  read-write
    STATUS      current
    DESCRIPTION
        "Enable or disable cut-Through for priority 5."
    DEFVAL { false }
    ::= { rlIfInterfaces 24 }

rlIfCutPrioritySix OBJECT-TYPE
    SYNTAX      TruthValue
    MAX-ACCESS  read-write
    STATUS      current
    DESCRIPTION
        "Enable or disable cut-Through for priority 6."
    DEFVAL { false }
    ::= { rlIfInterfaces 25 }

rlIfCutPrioritySeven OBJECT-TYPE
    SYNTAX      TruthValue
    MAX-ACCESS  read-write
    STATUS      current
    DESCRIPTION
        "Enable or disable cut-Through for priority 7."
    DEFVAL { false }
    ::= { rlIfInterfaces 26 }

rlIfCutThroughTable    OBJECT-TYPE
   SYNTAX  SEQUENCE  OF RlIfCutThroughEntry
   MAX-ACCESS   not-accessible
   STATUS       current
   DESCRIPTION
    "Information and configuration of cut-through feature."
   ::=  { rlIfInterfaces 27 }

rlIfCutThroughEntry OBJECT-TYPE
   SYNTAX  RlIfCutThroughEntry
   MAX-ACCESS   not-accessible
   STATUS       current
   DESCRIPTION
    "Defines the contents of each line in the swIfTable table."
   INDEX   { swIfIndex }
   ::=  { rlIfCutThroughTable 1 }

RlIfCutThroughEntry ::= SEQUENCE {
        rlIfCutThroughPriorityEnable                            TruthValue,
        rlIfCutThroughUntaggedEnable                            TruthValue,
        rlIfCutThroughOperMode                                  TruthValue
    }

rlIfCutThroughPriorityEnable  OBJECT-TYPE
    SYNTAX      TruthValue
    MAX-ACCESS  read-write
    STATUS      current
    DESCRIPTION
        "Enable or disable cut-through for a priority for an interface."
    DEFVAL { false }
    ::= {  rlIfCutThroughEntry 1  }

rlIfCutThroughUntaggedEnable  OBJECT-TYPE
    SYNTAX      TruthValue
    MAX-ACCESS  read-write
    STATUS      current
    DESCRIPTION
        "Enable or disable cut-through for untagged packets for an interface."
    DEFVAL { false }
    ::= {  rlIfCutThroughEntry 2  }

rlIfCutThroughOperMode  OBJECT-TYPE
    SYNTAX      TruthValue
    MAX-ACCESS  read-only
    STATUS      current
    DESCRIPTION
        "Operational mode of spesific cut-through interface."
    ::= {  rlIfCutThroughEntry 3  }

rlCutThroughPacketLength OBJECT-TYPE
    SYNTAX      INTEGER
    MAX-ACCESS  read-only
    STATUS      current
    DESCRIPTION
        "The default packet length that is assigned to a packet in the
         Cut-Through mode."
    ::= { rlIfInterfaces 28 }

rlCutThroughPacketLengthAfterReset OBJECT-TYPE
    SYNTAX      INTEGER (257 .. 16383)
    MAX-ACCESS  read-write
    STATUS      current
    DESCRIPTION
        "The default packet length that is assigned to a packet in the
         Cut-Through mode after reset."
    DEFVAL { 1522 }
    ::= { rlIfInterfaces 29 }

rlCutThroughEnable OBJECT-TYPE
    SYNTAX      TruthValue
    MAX-ACCESS  read-only
    STATUS      current
    DESCRIPTION
        "Cut-Through global enable mode."
    ::= { rlIfInterfaces 30 }

rlCutThroughEnableAfterReset OBJECT-TYPE
    SYNTAX      TruthValue
    MAX-ACCESS  read-write
    STATUS      current
    DESCRIPTION
        "Cut-Through global enable mode after reset."
    DEFVAL { false }
    ::= { rlIfInterfaces 31 }

rlFlowControlMode OBJECT-TYPE
    SYNTAX      INTEGER {
        send-receive(1),
        receive-only(2)
        }
    MAX-ACCESS  read-write
    STATUS      current
    DESCRIPTION
        "Define which mode will be enabled on flow control enabled ports.
        The interfaces with enabled flow control will receive pause frames, but will not send flow control pause
        frames
        Send-receive: The interfaces with enabled flow control will receive and send pause frames.
        Receive-only: The interfaces with enabled flow control will receive pause frames, but will not send flow
       control pause frames."

    ::= { rlIfInterfaces 32 }
rlIfPortsNegotationTuning OBJECT-TYPE
    SYNTAX      TruthValue
    MAX-ACCESS  read-write
    STATUS      current
    DESCRIPTION
        "indicates if to apply link negotiation tuning WA globally for all ports with PHY 3140."
    ::= { rlIfInterfaces 33 }

rlFlowControlPerSystem OBJECT-TYPE
    SYNTAX      TruthValue
    MAX-ACCESS  read-write
    STATUS      current
    DESCRIPTION
        "define if flow control is enabled on all regular ports and trunk in the system or not."
    ::= { rlIfInterfaces 34 }

rlMacOperationTable    OBJECT-TYPE
   SYNTAX  SEQUENCE  OF MacOperationEntry
   MAX-ACCESS   not-accessible
   STATUS       current
   DESCRIPTION
    "pefrom mac operation on given ifindex"
   ::=  { swInterfaces 8 }

macOperationEntry OBJECT-TYPE
   SYNTAX  MacOperationEntry
   MAX-ACCESS   not-accessible
   STATUS       current
   DESCRIPTION
    "Defines mac operation "
   INDEX   { macOpifIndex }
   ::=  { rlMacOperationTable 1 }

MacOperationEntry ::= SEQUENCE {
        macOpifIndex                        INTEGER,
		macOpType                           INTEGER
	}

macOpifIndex OBJECT-TYPE
    SYNTAX   INTEGER
    MAX-ACCESS  read-only
    STATUS      current
    DESCRIPTION
        "Index to the rlMacOperationTable. The interface defined by a
         particular value of this index is the same interface as
         identified by the same value of ifIndex (MIB II)."
    ::= {  macOperationEntry 1  }

macOpType OBJECT-TYPE
    SYNTAX  INTEGER {
        securePortDynamicToStatic(1),
		securePortClearStatic(2)
    }
    MAX-ACCESS  read-write
    STATUS      current
    DESCRIPTION
        " This variable indicates what operation should be performed on the MAC
          of the given interface."
    ::= {  macOperationEntry 2  }

NumOfLanesBits ::= TEXTUAL-CONVENTION
    STATUS  current
    DESCRIPTION
        "num of lanes for interface mode in speed bits."
    SYNTAX BITS {
		default(0),
        oneLane(1),
        twoLanes(2),
        fourLanes(3),
        eightLanes(4)
    }

rlIfApPortTable    OBJECT-TYPE
   SYNTAX  SEQUENCE  OF RlIfApPortEntry
   MAX-ACCESS   not-accessible
   STATUS       current
   DESCRIPTION
    "Information and configuration of AP advertisements feature."
   ::=  { rlIfInterfaces 35 }

rlIfApPortEntry OBJECT-TYPE
   SYNTAX  RlIfApPortEntry
   MAX-ACCESS   not-accessible
   STATUS       current
   DESCRIPTION
    "Defines the contents of each line in the rlIfApPortTable table."
   INDEX   { rlIfApPortIndex, rlIfApPortSpeed }
   ::=  { rlIfApPortTable 1 }

RlIfApPortEntry ::= SEQUENCE {
    rlIfApPortIndex                                         INTEGER,
	rlIfApPortSpeed                                         INTEGER,
    rlIfApPortFcFecSupported	                            INTEGER,
    rlIfApPortRsFecSupported                                INTEGER,
	rlIfApPortFecRequired	                                INTEGER,
	rlIfApPortNumOfLanesBmp					                NumOfLanesBits,
    rlIfApPortRs544514FecSupported                          INTEGER
}

rlIfApPortIndex OBJECT-TYPE
    SYNTAX   INTEGER
    MAX-ACCESS  read-only
    STATUS      current
    DESCRIPTION
        "Index to the swIfApTable. The interface defined by a
         particular value of this index is the same interface as
         identified by the same value of ifIndex (MIB II)."
    ::= {  rlIfApPortEntry 1  }

rlIfApPortSpeed OBJECT-TYPE
   SYNTAX  INTEGER
   MAX-ACCESS   read-write
   STATUS       current
   DESCRIPTION
        "This variable specifies the required speed of this interface in bits
         per second. This specification will take effect only if
         swIfSpeedDuplexAutoNegotiation is disabled.
         A value of 10 is returned for 10G.
         A value of 0 is returned if the value of the variable
         hasn't been set."
   DEFVAL { 0 }
  ::= { rlIfApPortEntry  2 }

rlIfApPortFcFecSupported  OBJECT-TYPE
    SYNTAX  INTEGER {
        default(0),
        true(1),
        false(2)
    }
    MAX-ACCESS  read-write
    STATUS      current
    DESCRIPTION
        "Enable or disable support FC fec on an interface."
    DEFVAL { default }
    ::= {  rlIfApPortEntry 3 }

rlIfApPortRsFecSupported  OBJECT-TYPE
    SYNTAX  INTEGER {
        default(0),
        true(1),
        false(2)
    }
    MAX-ACCESS  read-write
    STATUS      current
    DESCRIPTION
        "Enable or disable support RS fec on an interface."
    DEFVAL { default }
    ::= {  rlIfApPortEntry 4 }

rlIfApPortFecRequired  OBJECT-TYPE
    SYNTAX  INTEGER {
        default(0),
        true(1),
        false(2)
    }
    MAX-ACCESS  read-write
    STATUS      current
    DESCRIPTION
        "Required or not required fec from link partner."
    DEFVAL { default }
    ::= {  rlIfApPortEntry 5 }

rlIfApPortNumOfLanesBmp OBJECT-TYPE
    SYNTAX NumOfLanesBits
    MAX-ACCESS   read-write
    STATUS       current
    DESCRIPTION
        "num of lanes to advertize per speed for interface mode."
    DEFVAL { {default} }
    ::= { rlIfApPortEntry 6 }

rlIfApPortRs544514FecSupported OBJECT-TYPE
    SYNTAX  INTEGER {
        default(0),
        true(1),
        false(2)
    }
    MAX-ACCESS  read-write
    STATUS      current
    DESCRIPTION
        "Enable or disable support RS(544,514) fec on an interface."
    DEFVAL { default }
    ::= {  rlIfApPortEntry 7 }

rlLstGroupIdTable    OBJECT-TYPE
   SYNTAX  SEQUENCE  OF RlLstGroupIdEntry
   MAX-ACCESS   not-accessible
   STATUS       current
   DESCRIPTION
    "Information about LST group-ids."
   ::=  { rlIfInterfaces 36 }

rlLstGroupIdEntry OBJECT-TYPE
   SYNTAX  RlLstGroupIdEntry
   MAX-ACCESS   not-accessible
   STATUS       current
   DESCRIPTION
    "Defines the contents of each line in the rlLstGroupIdTable table."
   INDEX   { rlLstGroupIdIndex }
   ::=  { rlLstGroupIdTable 1 }

RlLstGroupIdEntry ::= SEQUENCE {
    rlLstGroupIdIndex                 INTEGER,
	rlLstGroupIdEnable                TruthValue,
    rlLstGroupIdStatus                INTEGER,
    rlLstGroupIdUpstreamPortList      PortList,
    rlLstGroupIdDownstreamPortList    PortList,
	rlLstGroupIdMode                  INTEGER
}

rlLstGroupIdIndex OBJECT-TYPE
    SYNTAX   INTEGER
    MAX-ACCESS  read-write
    STATUS      current
    DESCRIPTION
        "Index to the rlLstGroupIdTable."
    ::= {  rlLstGroupIdEntry 1  }

rlLstGroupIdEnable OBJECT-TYPE
   SYNTAX       TruthValue
   MAX-ACCESS   read-write
   STATUS       current
   DESCRIPTION
        "Enable or Disable the LST group."
   DEFVAL { false }
  ::= { rlLstGroupIdEntry 2 }

rlLstGroupIdStatus  OBJECT-TYPE
    SYNTAX  INTEGER {
        up(1),
        down(2)
    }
    MAX-ACCESS  read-only
    STATUS      current
    DESCRIPTION
        "The operative status of the LST group according to its upstream members."
    ::= {  rlLstGroupIdEntry 3  }

rlLstGroupIdUpstreamPortList  OBJECT-TYPE
    SYNTAX      PortList
    MAX-ACCESS  read-only
    STATUS      current
    DESCRIPTION
        "Indicates which ports/trunks of this LST group are upstream members."
    ::= {  rlLstGroupIdEntry 4  }

rlLstGroupIdDownstreamPortList  OBJECT-TYPE
    SYNTAX      PortList
    MAX-ACCESS  read-only
    STATUS      current
    DESCRIPTION
        "Indicates which ports/trunks of this LST group are downstream members."
    ::= {  rlLstGroupIdEntry 5  }

rlLstGroupIdMode  OBJECT-TYPE
    SYNTAX  INTEGER {
        and(1),
        or(2)
    }
    MAX-ACCESS  read-write
    STATUS      current
    DESCRIPTION
        "Defines the LST group mode."
    ::= {  rlLstGroupIdEntry 6  }

rlLstMembershipInterfaceTable    OBJECT-TYPE
   SYNTAX  SEQUENCE  OF RlLstMembershipInterfaceEntry
   MAX-ACCESS   not-accessible
   STATUS       current
   DESCRIPTION
    "Information about LST interfaces."
   ::=  { rlIfInterfaces 37 }

rlLstMembershipInterfaceEntry OBJECT-TYPE
   SYNTAX  RlLstMembershipInterfaceEntry
   MAX-ACCESS   not-accessible
   STATUS       current
   DESCRIPTION
    "Defines the contents of each line in the rlLstGroupIdTable table."
   INDEX   { rlLstMembershipInterfaceIndex, rlLstMembershipInterfaceGroupIdIndex }
   ::=  { rlLstMembershipInterfaceTable 1 }

RlLstMembershipInterfaceEntry ::= SEQUENCE {
    rlLstMembershipInterfaceIndex           INTEGER,
	rlLstMembershipInterfaceGroupIdIndex    INTEGER,
    rlLstMembershipInterfaceType            INTEGER,
    rlLstMembershipInterfaceStatus          INTEGER,
    rlLstMembershipInterfaceRowStatus       RowStatus
}

rlLstMembershipInterfaceIndex OBJECT-TYPE
    SYNTAX      INTEGER
    MAX-ACCESS  read-write
    STATUS      current
    DESCRIPTION
        "Index to the rlLstMembershipInterfaceTable."
    ::= {  rlLstMembershipInterfaceEntry 1  }

rlLstMembershipInterfaceGroupIdIndex OBJECT-TYPE
   SYNTAX       INTEGER
   MAX-ACCESS   read-write
   STATUS       current
   DESCRIPTION
        "LST group-id Index."
  ::= { rlLstMembershipInterfaceEntry 2 }

rlLstMembershipInterfaceType  OBJECT-TYPE
    SYNTAX  INTEGER {
        upstream(1),
        downstream(2)
    }
    MAX-ACCESS  read-write
    STATUS      current
    DESCRIPTION
        "Defines the interface as an upstream or downstream interface in the group."
    ::= {  rlLstMembershipInterfaceEntry 3  }

rlLstMembershipInterfaceStatus  OBJECT-TYPE
    SYNTAX  INTEGER {
        up(1),
        down(2),
        disabled(3)
    }
    MAX-ACCESS  read-only
    STATUS      current
    DESCRIPTION
        "The status of the LST interface according to its link state."
    ::= {  rlLstMembershipInterfaceEntry 4  }

rlLstMembershipInterfaceRowStatus  OBJECT-TYPE
    SYNTAX      RowStatus
    MAX-ACCESS  read-write
    STATUS      current
    DESCRIPTION
        "Row status for the specific LST interface and group-id."
    ::= {  rlLstMembershipInterfaceEntry 5  }

rlNeighborStatusWDEnable OBJECT-TYPE
    SYNTAX      TruthValue
    MAX-ACCESS  read-write
    STATUS      current
    DESCRIPTION
        "Enable or Disable neighbor status watchdog feature.
		 This field is set to false if the neighbor status watchdog timer expires."
    ::= { rlIfInterfaces 38 }

rlNeighborStatusWDTimerInterval OBJECT-TYPE
    SYNTAX      INTEGER (30 .. 600)
    MAX-ACCESS  read-write
    STATUS      current
    DESCRIPTION
        "define neighbor status watchdog timer interval in seconds."
    ::= { rlIfInterfaces 39 }

rlNeighborStatusWDFileName OBJECT-TYPE
    SYNTAX      DisplayString (SIZE(0..160))
    MAX-ACCESS  read-write
    STATUS      current
    DESCRIPTION
        "define the file name that will be in root directory in flash.
		The last file provided in WCD post is the relevant file to execute when
		neighbor status watchdog timer is expired."
    ::= { rlIfInterfaces 40 }

rlNeighborStatusWDNumOfPollingGetCounter OBJECT-TYPE
    SYNTAX      INTEGER
    MAX-ACCESS  read-only
    STATUS      current
    DESCRIPTION
        "Counter that is incremented in each Get operation from WCD.
         Value is set to 0 when neighbor status watchdog is disabled or
		 in case neighbor status watchdog timer is expired."
    ::= { rlIfInterfaces 41 }

rlNeighborStatusWDStatus OBJECT-TYPE
    SYNTAX  INTEGER {
        active(1),
        inactive(2),
		expired(3)
    }
    MAX-ACCESS  read-only
    STATUS      current
    DESCRIPTION
        "define the status neighbor status watchdog.
		 expired is when the watchdog timer expires (and rlNeighborStatusWDEnable changed to false) -
         it is to indicate that watchdog is disabled due to timer expiring
		 and not due to user action."
    ::= { rlIfInterfaces 42 }

rlifPresentTable OBJECT-TYPE
    SYNTAX  SEQUENCE OF RlifPresentEntry
    MAX-ACCESS   not-accessible
    STATUS       current
    DESCRIPTION
            "A list of present interface entries. The number of
            entries is given by the value of ifNumber. This table
            provides the same information as ifTable but filtered
            to show only interfaces that are physically present."
   ::=  { rlIfInterfaces 43 }

rlifPresentEntry OBJECT-TYPE
    SYNTAX  RlifPresentEntry
    MAX-ACCESS   not-accessible
    STATUS       current
    DESCRIPTION
            "A present interface entry containing objects at the
            subnetwork layer and below for a particular
            interface. This entry mirrors ifEntry but only for
            present interfaces."
    INDEX       { rlifPresentIndex }
    ::= { rlifPresentTable 1 }

RlifPresentEntry ::=
               SEQUENCE {
                   rlifPresentIndex                 InterfaceIndex,
                   rlifPresentDescr                 DisplayString,
                   rlifPresentType                  IANAifType,
                   rlifPresentMtu                   Integer32,
                   rlifPresentSpeed                 Gauge32,
                   rlifPresentPhysAddress           PhysAddress,
                   rlifPresentAdminStatus           INTEGER,
                   rlifPresentOperStatus            INTEGER,
                   rlifPresentLastChange            TimeTicks,
                   rlifPresentInOctets              Counter64,
                   rlifPresentInUcastPkts           Counter32,
                   rlifPresentInNUcastPkts          Counter64,  -- deprecated
                   rlifPresentInDiscards            Counter64,
                   rlifPresentInErrors                 Counter64,
                   rlifPresentInUnknownProtos          Counter64,
                   rlifPresentOutOctets                Counter64,
                   rlifPresentOutUcastPkts             Counter32,
                   rlifPresentOutNUcastPkts            Counter64,  -- deprecated
                   rlifPresentOutDiscards              Counter64,
                   rlifPresentOutErrors                Counter64,
                   rlifPresentOutQLen                  Gauge32,    -- deprecated
                   rlifPresentSpecific                 OBJECT IDENTIFIER, -- deprecated
                   rlifPresentName                     DisplayString,
                   rlifPresentInMulticastPkts          Counter32,
                   rlifPresentInBroadcastPkts          Counter32,
                   rlifPresentOutMulticastPkts         Counter32,
                   rlifPresentOutBroadcastPkts         Counter32,
                   rlifPresentHCInOctets               Counter64,
                   rlifPresentHCInUcastPkts            Counter64,
                   rlifPresentHCInMulticastPkts        Counter64,
                   rlifPresentHCInBroadcastPkts        Counter64,
                   rlifPresentHCOutOctets              Counter64,
                   rlifPresentHCOutUcastPkts           Counter64,
                   rlifPresentHCOutMulticastPkts       Counter64,
                   rlifPresentHCOutBroadcastPkts       Counter64,
                   rlifPresentLinkUpDownTrapEnable     INTEGER,
                   rlifPresentHighSpeed                Gauge32,
                   rlifPresentPromiscuousMode          TruthValue,
                   rlifPresentConnectorPresent         TruthValue,
                   rlifPresentAlias                    DisplayString,
                   rlifPresentCounterDiscontinuityTime TimeStamp
               }

           rlifPresentIndex OBJECT-TYPE
               SYNTAX      InterfaceIndex
               MAX-ACCESS  read-only
               STATUS      current
               DESCRIPTION
                       "A unique value, greater than zero, for each
                       interface.  It is recommended that values are assigned
                       contiguously starting from 1.  The value for each
                       interface sub-layer must remain constant at least from
                       one re-initialization of the entity's network
                       management system to the next re-initialization."
               ::= { rlifPresentEntry 1 }

           rlifPresentDescr OBJECT-TYPE
               SYNTAX      DisplayString (SIZE (0..255))
               MAX-ACCESS  read-only
               STATUS      current
               DESCRIPTION
                       "A textual string containing information about the
                       interface.  This string should include the name of the
                       manufacturer, the product name and the version of the
                       interface hardware/software."
               ::= { rlifPresentEntry 2 }

           rlifPresentType OBJECT-TYPE
               SYNTAX      IANAifType
               MAX-ACCESS  read-only
               STATUS      current
               DESCRIPTION
                       "The type of interface.  Additional values for ifType
                       are assigned by the Internet Assigned Numbers
                       Authority (IANA), through updating the syntax of the
                       IANAifType textual convention."
               ::= { rlifPresentEntry 3 }

           rlifPresentMtu OBJECT-TYPE
               SYNTAX      Integer32
               MAX-ACCESS  read-only
               STATUS      current
               DESCRIPTION
                       "The size of the largest packet which can be
                       sent/received on the interface, specified in octets.
                       For interfaces that are used for transmitting network
                       datagrams, this is the size of the largest network
                       datagram that can be sent on the interface."
               ::= { rlifPresentEntry 4 }

           rlifPresentSpeed OBJECT-TYPE
               SYNTAX      Gauge32
               MAX-ACCESS  read-only
               STATUS      current
               DESCRIPTION
                       "An estimate of the interface's current bandwidth in
                       bits per second.  For interfaces which do not vary in
                       bandwidth or for those where no accurate estimation
                       can be made, this object should contain the nominal
                       bandwidth.  If the bandwidth of the interface is
                       greater than the maximum value reportable by this
                       object then this object should report its maximum
                       value (4,294,967,295) and ifHighSpeed must be used to
                       report the interace's speed.  For a sub-layer which
                       has no concept of bandwidth, this object should be
                       zero."
               ::= { rlifPresentEntry 5 }

           rlifPresentPhysAddress OBJECT-TYPE
               SYNTAX      PhysAddress
               MAX-ACCESS  read-only
               STATUS      current
               DESCRIPTION
                       "The interface's address at its protocol sub-layer.
                       For example, for an 802.x interface, this object
                       normally contains a MAC address.  The interface's
                       media-specific MIB must define the bit and byte
                       ordering and the format of the value of this object.
                       For interfaces which do not have such an address
                       (e.g., a serial line), this object should contain an
                       octet string of zero length."
               ::= { rlifPresentEntry 6 }

           rlifPresentAdminStatus OBJECT-TYPE
               SYNTAX  INTEGER {
                           up(1),       -- ready to pass packets
                           down(2),
                           testing(3)   -- in some test mode
                       }
               MAX-ACCESS  read-write
               STATUS      current
               DESCRIPTION
                       "The desired state of the interface.  The testing(3)
                       state indicates that no operational packets can be
                       passed.  When a managed system initializes, all
                       interfaces start with ifAdminStatus in the down(2)
                       state.  As a result of either explicit management
                       action or per configuration information retained by
                       the managed system, ifAdminStatus is then changed to
                       either the up(1) or testing(3) states (or remains in
                       the down(2) state)."
               ::= { rlifPresentEntry 7 }

           rlifPresentOperStatus OBJECT-TYPE
               SYNTAX  INTEGER {
                           up(1),        -- ready to pass packets
                           down(2),
                           testing(3),   -- in some test mode
                           unknown(4),   -- status can not be determined
                                         -- for some reason.
                           dormant(5),
                           notPresent(6),    -- some component is missing
                           lowerLayerDown(7) -- down due to state of
                                             -- lower-layer interface(s)
                       }
               MAX-ACCESS  read-only
               STATUS      current
               DESCRIPTION
                       "The current operational state of the interface.  The
                       testing(3) state indicates that no operational packets
                       can be passed.  If ifAdminStatus is down(2) then
                       ifOperStatus should be down(2).  If ifAdminStatus is
                       changed to up(1) then ifOperStatus should change to
                       up(1) if the interface is ready to transmit and
                       receive network traffic; it should change to
                       dormant(5) if the interface is waiting for external
                       actions (such as a serial line waiting for an incoming
                       connection); it should remain in the down(2) state if
                       and only if there is a fault that prevents it from
                       going to the up(1) state; it should remain in the
                       notPresent(6) state if the interface has missing
                       (typically, hardware) components."
               ::= { rlifPresentEntry 8 }

           rlifPresentLastChange OBJECT-TYPE
               SYNTAX      TimeTicks
               MAX-ACCESS  read-only
               STATUS      current
               DESCRIPTION
                       "The value of sysUpTime at the time the interface
                       entered its current operational state.  If the current
                       state was entered prior to the last re-initialization
                       of the local network management subsystem, then this
                       object contains a zero value."
               ::= { rlifPresentEntry 9 }

           rlifPresentInOctets OBJECT-TYPE
               SYNTAX      Counter64
               MAX-ACCESS  read-only
               STATUS      current
               DESCRIPTION
                       "The total number of octets received on the interface,
                       including framing characters.

                       Discontinuities in the value of this counter can occur
                       at re-initialization of the management system, and at
                       other times as indicated by the value of
                       ifCounterDiscontinuityTime."
               ::= { rlifPresentEntry 10 }

           rlifPresentInUcastPkts OBJECT-TYPE
               SYNTAX      Counter32
               MAX-ACCESS  read-only
               STATUS      current
               DESCRIPTION
                       "The number of packets, delivered by this sub-layer to
                       a higher (sub-)layer, which were not addressed to a
                       multicast or broadcast address at this sub-layer.

                       Discontinuities in the value of this counter can occur
                       at re-initialization of the management system, and at
                       other times as indicated by the value of
                       ifCounterDiscontinuityTime."
               ::= { rlifPresentEntry 11 }

           rlifPresentInNUcastPkts OBJECT-TYPE
               SYNTAX  Counter64
               MAX-ACCESS  read-only
               STATUS      deprecated
               DESCRIPTION
                       "The number of packets, delivered by this sub-layer to
                       a higher (sub-)layer, which were addressed to a
                       multicast or broadcast address at this sub-layer.

                       Discontinuities in the value of this counter can occur
                       at re-initialization of the management system, and at
                       other times as indicated by the value of
                       ifCounterDiscontinuityTime.

                       This object is deprecated in favour of
                       ifInMulticastPkts and ifInBroadcastPkts."
               ::= { rlifPresentEntry 12 }

           rlifPresentInDiscards OBJECT-TYPE
               SYNTAX      Counter64
               MAX-ACCESS  read-only
               STATUS      current
               DESCRIPTION
                       "The number of inbound packets which were chosen to be
                       discarded even though no errors had been detected to
                       prevent their being deliverable to a higher-layer
                       protocol.  One possible reason for discarding such a
                       packet could be to free up buffer space.

                       Discontinuities in the value of this counter can occur
                       at re-initialization of the management system, and at
                       other times as indicated by the value of
                       ifCounterDiscontinuityTime."
               ::= { rlifPresentEntry 13 }

           rlifPresentInErrors OBJECT-TYPE
               SYNTAX      Counter64
               MAX-ACCESS  read-only
               STATUS      current
               DESCRIPTION
                       "For packet-oriented interfaces, the number of inbound
                       packets that contained errors preventing them from
                       being deliverable to a higher-layer protocol.  For
                       character-oriented or fixed-length interfaces, the
                       number of inbound transmission units that contained
                       errors preventing them from being deliverable to a
                       higher-layer protocol.

                       Discontinuities in the value of this counter can occur
                       at re-initialization of the management system, and at
                       other times as indicated by the value of
                       ifCounterDiscontinuityTime."
               ::= { rlifPresentEntry 14 }

           rlifPresentInUnknownProtos OBJECT-TYPE
               SYNTAX      Counter64
               MAX-ACCESS  read-only
               STATUS      current
               DESCRIPTION
                       "For packet-oriented interfaces, the number of packets
                       received via the interface which were discarded
                       because of an unknown or unsupported protocol.  For
                       character-oriented or fixed-length interfaces that
                       support protocol multiplexing the number of
                       transmission units received via the interface which
                       were discarded because of an unknown or unsupported
                       protocol.  For any interface that does not support
                       protocol multiplexing, this counter will always be 0.

                       Discontinuities in the value of this counter can occur
                       at re-initialization of the management system, and at
                       other times as indicated by the value of
                       ifCounterDiscontinuityTime."
               ::= { rlifPresentEntry 15 }

           rlifPresentOutOctets OBJECT-TYPE
               SYNTAX      Counter64
               MAX-ACCESS  read-only
               STATUS      current
               DESCRIPTION
                       "The total number of octets transmitted out of the
                       interface, including framing characters.

                       Discontinuities in the value of this counter can occur
                       at re-initialization of the management system, and at
                       other times as indicated by the value of
                       ifCounterDiscontinuityTime."
               ::= { rlifPresentEntry 16 }

           rlifPresentOutUcastPkts OBJECT-TYPE
               SYNTAX      Counter32
               MAX-ACCESS  read-only
               STATUS      current
               DESCRIPTION
                       "The total number of packets that higher-level
                       protocols requested be transmitted, and which were not
                       addressed to a multicast or broadcast address at this
                       sub-layer, including those that were discarded or not
                       sent.

                       Discontinuities in the value of this counter can occur
                       at re-initialization of the management system, and at
                       other times as indicated by the value of
                       ifCounterDiscontinuityTime."
               ::= { rlifPresentEntry 17 }

           rlifPresentOutNUcastPkts OBJECT-TYPE
               SYNTAX      Counter64
               MAX-ACCESS  read-only
               STATUS      deprecated
               DESCRIPTION
                       "The total number of packets that higher-level
                       protocols requested be transmitted, and which were
                       addressed to a multicast or broadcast address at this
                       sub-layer, including those that were discarded or not
                       sent.

                       Discontinuities in the value of this counter can occur
                       at re-initialization of the management system, and at
                       other times as indicated by the value of
                       ifCounterDiscontinuityTime.
                       This object is deprecated in favour of
                       ifOutMulticastPkts and ifOutBroadcastPkts."
               ::= { rlifPresentEntry 18 }

           rlifPresentOutDiscards OBJECT-TYPE
               SYNTAX      Counter64
               MAX-ACCESS  read-only
               STATUS      current
               DESCRIPTION
                       "The number of outbound packets which were chosen to
                       be discarded even though no errors had been detected
                       to prevent their being transmitted.  One possible
                       reason for discarding such a packet could be to free
                       up buffer space.

                       Discontinuities in the value of this counter can occur
                       at re-initialization of the management system, and at
                       other times as indicated by the value of
                       ifCounterDiscontinuityTime."
               ::= { rlifPresentEntry 19 }

           rlifPresentOutErrors OBJECT-TYPE
               SYNTAX      Counter64
               MAX-ACCESS  read-only
               STATUS      current
               DESCRIPTION
                       "For packet-oriented interfaces, the number of
                       outbound packets that could not be transmitted because
                       of errors.  For character-oriented or fixed-length
                       interfaces, the number of outbound transmission units
                       that could not be transmitted because of errors.

                       Discontinuities in the value of this counter can occur
                       at re-initialization of the management system, and at
                       other times as indicated by the value of
                       ifCounterDiscontinuityTime."
               ::= { rlifPresentEntry 20 }

           rlifPresentOutQLen OBJECT-TYPE
               SYNTAX      Gauge32
               MAX-ACCESS  read-only
               STATUS      deprecated
               DESCRIPTION
                       "The length of the output packet queue (in packets)."
               ::= { rlifPresentEntry 21 }

           rlifPresentSpecific OBJECT-TYPE
               SYNTAX      OBJECT IDENTIFIER
               MAX-ACCESS  read-only
               STATUS      deprecated
               DESCRIPTION
                       "A reference to MIB definitions specific to the
                       particular media being used to realize the interface.
                       It is recommended that this value point to an instance
                       of a MIB object in the media-specific MIB, i.e., that
                       this object have the semantics associated with the
                       InstancePointer textual convention defined in RFC
                       1903.  In fact, it is recommended that the media-
                       specific MIB specify what value ifSpecific should/can
                       take for values of ifType.  If no MIB definitions
                       specific to the particular media are available, the
                       value should be set to the OBJECT IDENTIFIER { 0 0 }."
               ::= { rlifPresentEntry 22 }

           rlifPresentName OBJECT-TYPE
               SYNTAX      DisplayString
               MAX-ACCESS  read-only
               STATUS      current
               DESCRIPTION
                       "The textual name of the interface.  The value of this
                       object should be the name of the interface as assigned
                       by the local device and should be suitable for use in
                       commands entered at the device's `console'.  This
                       might be a text name, such as `le0' or a simple port
                       number, such as `1', depending on the interface naming
                       syntax of the device.  If several entries in the
                       ifTable together represent a single interface as named
                       by the device, then each will have the same value of
                       ifName.  Note that for an agent which responds to SNMP
                       queries concerning an interface on some other
                       (proxied) device, then the value of ifName for such an
                       interface is the proxied device's local name for it.

                       If there is no local name, or this object is otherwise
                       not applicable, then this object contains a zero-
                       length string."
               ::= { rlifPresentEntry 23 }

           rlifPresentInMulticastPkts OBJECT-TYPE
               SYNTAX      Counter32
               MAX-ACCESS  read-only
               STATUS      current
               DESCRIPTION
                       "The number of packets, delivered by this sub-layer to
                       a higher (sub-)layer, which were addressed to a
                       multicast address at this sub-layer.  For a MAC layer
                       protocol, this includes both Group and Functional
                       addresses.

                       Discontinuities in the value of this counter can occur
                       at re-initialization of the management system, and at
                       other times as indicated by the value of
                       ifCounterDiscontinuityTime."
               ::= { rlifPresentEntry 24 }

           rlifPresentInBroadcastPkts OBJECT-TYPE
               SYNTAX      Counter32
               MAX-ACCESS  read-only
               STATUS      current
               DESCRIPTION
                       "The number of packets, delivered by this sub-layer to
                       a higher (sub-)layer, which were addressed to a
                       broadcast address at this sub-layer.

                       Discontinuities in the value of this counter can occur
                       at re-initialization of the management system, and at
                       other times as indicated by the value of
                       ifCounterDiscontinuityTime."
               ::= { rlifPresentEntry 25 }

           rlifPresentOutMulticastPkts OBJECT-TYPE
               SYNTAX      Counter32
               MAX-ACCESS  read-only
               STATUS      current
               DESCRIPTION
                       "The total number of packets that higher-level
                       protocols requested be transmitted, and which were
                       addressed to a multicast address at this sub-layer,
                       including those that were discarded or not sent.  For
                       a MAC layer protocol, this includes both Group and
                       Functional addresses.

                       Discontinuities in the value of this counter can occur
                       at re-initialization of the management system, and at
                       other times as indicated by the value of
                       ifCounterDiscontinuityTime."
               ::= { rlifPresentEntry 26 }

           rlifPresentOutBroadcastPkts OBJECT-TYPE
               SYNTAX      Counter32
               MAX-ACCESS  read-only
               STATUS      current
               DESCRIPTION
                       "The total number of packets that higher-level
                       protocols requested be transmitted, and which were
                       addressed to a broadcast address at this sub-layer,
                       including those that were discarded or not sent.

                       Discontinuities in the value of this counter can occur
                       at re-initialization of the management system, and at
                       other times as indicated by the value of
                       ifCounterDiscontinuityTime."
               ::= { rlifPresentEntry 27 }

           rlifPresentHCInOctets OBJECT-TYPE
               SYNTAX      Counter64
               MAX-ACCESS  read-only
               STATUS      current
               DESCRIPTION
                       "The total number of octets received on the interface,
                       including framing characters.  This object is a 64-bit
                       version of ifInOctets.

                       Discontinuities in the value of this counter can occur
                       at re-initialization of the management system, and at
                       other times as indicated by the value of
                       ifCounterDiscontinuityTime."
               ::= { rlifPresentEntry 28 }

           rlifPresentHCInUcastPkts OBJECT-TYPE
               SYNTAX      Counter64
               MAX-ACCESS  read-only
               STATUS      current
               DESCRIPTION
                       "The number of packets, delivered by this sub-layer to
                       a higher (sub-)layer, which were not addressed to a
                       multicast or broadcast address at this sub-layer.
                       This object is a 64-bit version of ifInUcastPkts.

                       Discontinuities in the value of this counter can occur
                       at re-initialization of the management system, and at
                       other times as indicated by the value of
                       ifCounterDiscontinuityTime."
               ::= { rlifPresentEntry 29 }

           rlifPresentHCInMulticastPkts OBJECT-TYPE
               SYNTAX      Counter64
               MAX-ACCESS  read-only
               STATUS      current
               DESCRIPTION
                       "The number of packets, delivered by this sub-layer to
                       a higher (sub-)layer, which were addressed to a
                       multicast address at this sub-layer.  For a MAC layer
                       protocol, this includes both Group and Functional
                       addresses.  This object is a 64-bit version of
                       ifInMulticastPkts.

                       Discontinuities in the value of this counter can occur
                       at re-initialization of the management system, and at
                       other times as indicated by the value of
                       ifCounterDiscontinuityTime."
               ::= { rlifPresentEntry 30 }

           rlifPresentHCInBroadcastPkts OBJECT-TYPE
               SYNTAX      Counter64
               MAX-ACCESS  read-only
               STATUS      current
               DESCRIPTION
                       "The number of packets, delivered by this sub-layer to
                       a higher (sub-)layer, which were addressed to a
                       broadcast address at this sub-layer.  This object is a
                       64-bit version of ifInBroadcastPkts.

                       Discontinuities in the value of this counter can occur
                       at re-initialization of the management system, and at
                       other times as indicated by the value of
                       ifCounterDiscontinuityTime."
               ::= { rlifPresentEntry 31 }

           rlifPresentHCOutOctets OBJECT-TYPE
               SYNTAX      Counter64
               MAX-ACCESS  read-only
               STATUS      current
               DESCRIPTION
                       "The total number of octets transmitted out of the
                       interface, including framing characters.  This object
                       is a 64-bit version of ifOutOctets.

                       Discontinuities in the value of this counter can occur
                       at re-initialization of the management system, and at
                       other times as indicated by the value of
                       ifCounterDiscontinuityTime."
               ::= { rlifPresentEntry 32 }

           rlifPresentHCOutUcastPkts OBJECT-TYPE
               SYNTAX      Counter64
               MAX-ACCESS  read-only
               STATUS      current
               DESCRIPTION
                       "The total number of packets that higher-level
                       protocols requested be transmitted, and which were not
                       addressed to a multicast or broadcast address at this
                       sub-layer, including those that were discarded or not
                       sent.  This object is a 64-bit version of
                       ifOutUcastPkts.

                       Discontinuities in the value of this counter can occur
                       at re-initialization of the management system, and at
                       other times as indicated by the value of
                       ifCounterDiscontinuityTime."
               ::= { rlifPresentEntry 33 }

           rlifPresentHCOutMulticastPkts OBJECT-TYPE
               SYNTAX      Counter64
               MAX-ACCESS  read-only
               STATUS      current
               DESCRIPTION
                       "The total number of packets that higher-level
                       protocols requested be transmitted, and which were
                       addressed to a multicast address at this sub-layer,
                       including those that were discarded or not sent.  For
                       a MAC layer protocol, this includes both Group and
                       Functional addresses.  This object is a 64-bit version
                       of ifOutMulticastPkts.
                       Discontinuities in the value of this counter can occur
                       at re-initialization of the management system, and at
                       other times as indicated by the value of
                       ifCounterDiscontinuityTime."
               ::= { rlifPresentEntry 34 }

           rlifPresentHCOutBroadcastPkts OBJECT-TYPE
               SYNTAX      Counter64
               MAX-ACCESS  read-only
               STATUS      current
               DESCRIPTION
                       "The total number of packets that higher-level
                       protocols requested be transmitted, and which were
                       addressed to a broadcast address at this sub-layer,
                       including those that were discarded or not sent.  This
                       object is a 64-bit version of ifOutBroadcastPkts.

                       Discontinuities in the value of this counter can occur
                       at re-initialization of the management system, and at
                       other times as indicated by the value of
                       ifCounterDiscontinuityTime."
               ::= { rlifPresentEntry 35 }

           rlifPresentLinkUpDownTrapEnable  OBJECT-TYPE
               SYNTAX      INTEGER { enabled(1), disabled(2) }
               MAX-ACCESS  read-write
               STATUS      current
               DESCRIPTION
                       "Indicates whether linkUp/linkDown traps should be
                       generated for this interface.

                       By default, this object should have the value
                       enabled(1) for interfaces which do not operate on
                       'top' of any other interface (as defined in the
                       ifStackTable), and disabled(2) otherwise."
               ::= { rlifPresentEntry 36 }

           rlifPresentHighSpeed OBJECT-TYPE
               SYNTAX      Gauge32
               MAX-ACCESS  read-only
               STATUS      current
               DESCRIPTION
                       "An estimate of the interface's current bandwidth in
                       units of 1,000,000 bits per second.  If this object
                       reports a value of `n' then the speed of the interface
                       is somewhere in the range of `n-500,000' to
                       `n+499,999'.  For interfaces which do not vary in
                       bandwidth or for those where no accurate estimation
                       can be made, this object should contain the nominal
                       bandwidth.  For a sub-layer which has no concept of
                       bandwidth, this object should be zero."
               ::= { rlifPresentEntry 37 }

           rlifPresentPromiscuousMode  OBJECT-TYPE
               SYNTAX      TruthValue
               MAX-ACCESS  read-write
               STATUS      current
               DESCRIPTION
                       "This object has a value of false(2) if this interface
                       only accepts packets/frames that are addressed to this
                       station.  This object has a value of true(1) when the
                       station accepts all packets/frames transmitted on the
                       media.  The value true(1) is only legal on certain
                       types of media.  If legal, setting this object to a
                       value of true(1) may require the interface to be reset
                       before becoming effective.

                       The value of ifPromiscuousMode does not affect the
                       reception of broadcast and multicast packets/frames by
                       the interface."
               ::= { rlifPresentEntry 38 }

           rlifPresentConnectorPresent   OBJECT-TYPE
               SYNTAX      TruthValue
               MAX-ACCESS  read-only
               STATUS      current
               DESCRIPTION
                       "This object has the value 'true(1)' if the interface
                       sublayer has a physical connector and the value
                       'false(2)' otherwise."
               ::= { rlifPresentEntry 39 }

           rlifPresentAlias   OBJECT-TYPE
               SYNTAX      DisplayString (SIZE(0..64))
               MAX-ACCESS  read-write
               STATUS      current
               DESCRIPTION
                       "This object is an 'alias' name for the interface as
                       specified by a network manager, and provides a non-
                       volatile 'handle' for the interface.

                       On the first instantiation of an interface, the value
                       of ifAlias associated with that interface is the
                       zero-length string.  As and when a value is written
                       into an instance of ifAlias through a network
                       management set operation, then the agent must retain
                       the supplied value in the ifAlias instance associated
                       with the same interface for as long as that interface
                       remains instantiated, including across all re-
                       initializations/reboots of the network management
                       system, including those which result in a change of
                       the interface's ifIndex value.

                       An example of the value which a network manager might
                       store in this object for a WAN interface is the
                       (Telco's) circuit number/identifier of the interface.

                       Some agents may support write-access only for
                       interfaces having particular values of ifType.  An
                       agent which supports write access to this object is
                       required to keep the value in non-volatile storage,
                       but it may limit the length of new values depending on
                       how much storage is already occupied by the current
                       values for other interfaces."
               ::= { rlifPresentEntry 40 }

           rlifPresentCounterDiscontinuityTime OBJECT-TYPE
               SYNTAX      TimeStamp
               MAX-ACCESS  read-only
               STATUS      current
               DESCRIPTION
                       "The value of sysUpTime on the most recent occasion at
                       which any one or more of this interface's counters
                       suffered a discontinuity.  The relevant counters are
                       the specific instances associated with this interface
                       of any Counter32 or Counter64 object contained in the
                       ifTable or ifXTable.  If no such discontinuities have
                       occurred since the last re-initialization of the local
                       management subsystem, then this object contains a zero
                       value."
               ::= { rlifPresentEntry 41 }

END
